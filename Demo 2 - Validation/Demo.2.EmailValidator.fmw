FME workspace Demo.2.EmailValidator.fmw

Parameters:
- FILE = D:\FME Projects\Demos\Input-Data\sports_club_membership.csv   # "" Select a File
- BadEmails = $(FME_MF_DIR)Output\Bad Emails.xlsx   # Destination Microsoft Excel File

Writers:
- XLSXW_1: XLSXW to $(BadEmails)

Note: A creator is used as an entry point to initiate workflows by generating a starting dataset or placeholder feature when no input data exists, allowing the workspace to execute without requiring an external data source.
Starting_Here: Creator
    GEOMTYPE = Geometry Object
    NUM = 1
    CREATED -> Read_data_from_CSV_File [INITIATOR]
Note: Reads the data from the spreadsheet
Note: Expand the following
Read_data_from_CSV_File: FeatureReader
    ATTRIBUTES = CSV,"FirstName,LastName,DOB,Email,Phone,Address,MembershipStartDate,MembershipStatus"
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = ,
    CSV2_DELIMITER_DETECTION_ALGORITHM = EQUAL_FIELDS_PER_LINE
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(FILE)
    FEATURETYPES = CSV
    FORMAT = CSV2
    INTERACT = NONE
    ORDER_RESULTS = No
    OUTPUT_ADD_SCHEMA_ATTRIBUTES = NO
    OUTPUT_FEATURES_DISPLAY = Schema and Data Features
    CSV -> Check_if_email_is_Valid

Bookmark: Check for Bad Emails
Check_if_email_is_Valid: Tester
    BOOL_OP = OR
    TEST_CLAUSE = CASE_SENSITIVE_TEST @Value(Email) CONTAINS_REGEX ^[a-zA-Z0-9._%+-]+@[a-zA-Z0-9.-]+\.[a-zA-Z]{2,}$
    TEST_MODE = CASE_SENSITIVE_TEST
    PASSED -> Logging_the_Good_Ones
    FAILED -> BadEmailList (writer XLSXW_1)

Bookmark: System Log
Logging_the_Good_Ones: Logger
    LOG_FEATURE = LOG_ONLY
    MAXCOORDS = 20
    MAXFEATS = 20
    MESSAGE = Feature is:
    SEVERITY = INFO

Bookmark: Outputs
BadEmailList (writer XLSXW_1)
    attributes: FirstName string(11), LastName string(10), DOB date(20), Email string(34), Phone string(22), Address string(56), MembershipStartDate date(20), MembershipStatus string(8)
